# software_requirements

## SFW0001: The Software must comunicate via Bluetooth (Functional)

### SFW0002: The Software must mantain a stable connection once the app is started (Functional)

### SFW0003: The must receive as data: Moving speed; Robot state; Robot orientation; Distance; Average Speed (Functional)

### SFW0004: The app must send as data:Moving speed; State change;Engine rotation; Engine state; Wheel angle (Functional)
State change refers to AUTO and MANUAL.
Engine rotation refers to foward and reverse.
Engine state refers to on and off.

## SFW0005: The software must have an User Interface (Functional)

### SFW0006: The interface must switch between AUTO and MANUAL mode (Functional)

### SFW0007: In AUTO screen, the should be able to monitor robot received data, in a 1Hz refresh rate (Functional)

### SFW0008: In MANUAL screen the user should be able to control the movement of the robot in directional mode (Functional)

### SFW0009: In any screen the user should be able to define the robot speed (Functional)

## SFW0010: The software data must be stored in short term memory, and get erased in app restart (Functional)
