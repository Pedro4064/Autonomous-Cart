# stakeholder_requirements

## STK0001: The Robot must have two different modes of operation: [AUTO] and [MANUAL] (Functional)
- Rationale: Since the robot must be able to autonomously navigate a path and also be able to be controled by cellphone.

## STK0002: The Robot must follow a predetermined path autonomously when in the [AUTO] mode (Functional)

### STK0003: The Robot must interpret a path, when in [AUTO] mode, as a white tape on a dark background (Functional)
- Rationale: The circuit the robot will need to follow is delimited by a white masking tape on a black matt.

### STK0004: The Robot, when in [AUTO] mode, must not deviate more than 3cm from the designated path (Functional)

### STK0005: The Robot, when in [AUTO] mode, must follow a path containing turns (of up to 360 deg) (Functional)
- Rationale: The circuit the robot must follow may include turns

### STK0006: The Robot, when in [AUTO] mode, must follow a path containing intersections by keeping its original heading (Functional)
- Rationale: The circuit that the robot must follow may consist of intersactions

## STK0007: The Robot, when in [AUTO] mode, must stop at the end of the circuit (Functional)

### STK0008: The Robot, when in [AUTO] mode, must interpret the end of the circuit as a series of 3 white lines on the ground perpendicular to its current heading (Functional)

## STK0009: The Robot's [ROBOT_MAX_SPEED], when in [AUTO] mode, must be configurable via cellphone (Functional)

## STK0010: The Robot's [ROBOT_PARAM], when in [AUTO] mode, must be remotely monitored via cellphone (Functional)

### STK0011: The Robot's [ROBOT_PARAM] must contain [ROBOT_TOTAL_DISTANCE] (Functional)

### STK0012: The Robot's [ROBOT_PARAM] must contain [ROBOT_CURRENT_SPEED] (Functional)

### STK0013: The Robot's [ROBOT_PARAM] must contain [ROBOT_AVG_SPEED] (Functional)

### STK0014: The Robot's [ROBOT_PARAM] must contain [ROBOT_ORIENTATION] (Functional)

### STK0015: The Robot's [ROBOT_PARAM], when in [AUTO] mode, must be updated as a 1Hz frequency (Functional)

## STK0016: The Robot, when in [MANUAL] mode, must be controled via cellphone (Functional)

## STK0017: The Robot must stop and sound an alarm when an obstacle is detected in front (Functional)

## STK0018: The Robot must stop moving when a collision is detected (Functional)

## #19 (Functional)
