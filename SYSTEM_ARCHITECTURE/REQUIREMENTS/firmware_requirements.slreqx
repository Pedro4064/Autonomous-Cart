# firmware_requirements
HLR for Autonomous Cart Firmware

## FMW0007: The Firmware must estimate the robot's [ROBOT_PARAM] at a 5 Hz rate (Functional)

## FWM0008: The Firmware, when in [AUTO] mode, must transfer wirelessly the robot's [ROBOT_PARAM] at a 1 Hz rate (Functional)

## FMW0010: The Firmware must capture [TELEMETRY_DATA] (Functional)

### FMW0001: The Firmware must store in [TELEMETRY_DATA] the IMU sensor values at 5 Hz rate (Functional)

### FMW0002: The Firmware must store in [TELEMETRY_DATA] the colision sensor values at a 5 Hz rate (Functional)

### FMW0003: The Firmware must store in [TELEMETRY_DATA] the line sensor values at a 5 Hz rate (Functional)

### FMW0004: The Firmware must store in [TELEMETRY_DATA] the ultrassonic sensor values at a 5 Hz rate (Functional)

### FMW0005: The Firmware must store in [TELEMETRY_DATA] the encoder count sensor values at a 5 Hz rate (Functional)

### FWM0006: The Firmware must store in [TELEMETRY_DATA] the battery voltage sensor values at a 5 Hz rate (Functional)

## FMW0011: The Firmware, when in [AUTO] mode, must transfer wirelessly the firmware's [TELEMETRY_DATA] at a 1 Hz rate (Functional)

## FMW0012: The Firmware must have two modes of operation, [AUTO] and [MANUAL] (Functional)

## FMW0013: The Firmware, when in [MANUAL] mode, must receive [MANUAL_COMMANDS] at a 5 Hz rate (Functional)

## FMW0014: The Firmware, when in [AUTO] mode, must indentify the predetermined path (Functional)

## FMW0015: The Firmware, when in [AUTO] mode, must identify the end of the path (Functional)

## FMW0016: The Firmware must stop the robot's motion when collision is detected (Functional)

## FMW0017: The Firmware must indetify as an obstacle any objects closer than 10cm (Functional)

## FMW0018: The Firmware, when an obstacle is identified, must stop the robot's motion (Functional)

## FMW0019: The Firmware, when an obstacle is identified, must ring an aural warning (Functional)

## FMW0020: The Firmware, when in [AUTO] mode, must calculate the necessary actuator commands for predetermined path following (Functional)
