# hardware_low_level_requirements

## HW001: Motion and Direction Control (Functional)

### HW002: Namiki 22CL-3501PG 80:1 Motors (Functional)
Brand: Namiki Coreless Motor (Japan)\nModel: 22CL-3501PG\nOperating Voltage: 12VDC\nRated Power: 15W\nStall Torque: 16.5kg*cm\nContinuous Torque: 5kg*cm\nDiameter: 22mm\nShaft Length: 19mm (with 90-degree double-cut)\nTotal Length: 65mm (includes gearbox and encoder)\nStall Current: 1.8A\nReduction Ratio: 80:1 (metal planetary reduction gear)\nOutput Speed: 120 RPM @ 12VDC\nWeight: 140g\nPhotoelectric Encoder: Includes photoelectric encoder output.

### HW003: H-Bridge L298N (Functional)
Will control the direction and speed of the motors.

### HW004: Left Motor Speed Control (Functional)
ARM Pin Name: PC0\nARM Peripheral: PWM TIM1_CH1

### HW005: Right Motor Speed Control (Functional)
ARM Pin Name: PC1\nARM Peripheral: PWM TIM1_CH2

### HW006: Left Motor Rotation Direction Control (Functional)
ARM Pin Name: PB12 / PB7\nARM Peripheral: GPIO_EXTI12 / GPIO_Output

### HW007: Right Motor Rotation Direction Control (Functional)
ARM Pin Name: PB9 / PA10\nARM Peripheral: GPIO_Output

## HW008: Obstacle and Collision Detection (Functional)

### HW009: Ultrasonic Sensor HC-SR04 (Functional)
Front sensor echo:\nARM Pin Name: PA4\nARM Peripheral: TIM3_CH2 (Timer - Capture)\nTrigger for all ultrasonic sensors:\nARM Pin Name: PB2\nARM Peripheral: PWM TIM20_CH1\nRear sensor echo:\nARM Pin Name: PB0\nARM Peripheral: TIM3_CH3 (Timer - Capture)\nLeft sensor echo:\nARM Pin Name: PB1\nARM Peripheral: TIM3_CH4 (Timer - Capture)\nRight sensor echo:\nARM Pin Name: PC6\nARM Peripheral: TIM3_CH1 (Timer - Capture)

### HW010: Micro-switch (collision sensor) (Functional)
ARM Pin Name: PD2 (Front collision sensor)\nARM Peripheral: GPIO_EXTI2

## HW011: Sensing and Monitoring (Functional)

### 3.1: MPU6050 Module (IMU) (Functional)
SPI SCK:\nARM Pin Name: PC10\nARM Peripheral: SPI3_SCK\nSPI MISO:\nARM Pin Name: PC11\nARM Peripheral: SPI3_MISO\nSPI MOSI:\nARM Pin Name: PC12\nARM Peripheral: SPI3_MOSI

### 3.2: Line Follower Module TCRT5000 (Functional)
IR Track Sensor 1:\nARM Pin Name: PA0\nARM Peripheral: ADC1_IN1\nIR Track Sensor 2:\nARM Pin Name: PA6\nARM Peripheral: ADC2_IN3\nIR Track Sensor 3:\nARM Pin Name: PB13\nARM Peripheral: ADC3_IN5\nIR Track Sensor 4:\nARM Pin Name: PB15\nARM Peripheral: ADC4_IN5\nIR Track Sensor 5:\nARM Pin Name: PA9\nARM Peripheral: ADC5_IN2

### 3.3: Encoder (Functional)
Left wheel encoder:\nARM Pin Name: PB4\nARM Peripheral: TIM16_CH1\nRight wheel encoder:\nARM Pin Name: PB5\nARM Peripheral: TIM17_CH1

## HW012: Interface and Communication (Functional)

### HW013: Bluetooth Module HC-05 (Functional)
UART TX:\nARM Pin Name: PB10\nARM Peripheral: USART3_TX\nUART RX:\nARM Pin Name: PB11\nARM Peripheral: USART3_RX

### HW014: Buzzer (Functional)
ARM Pin Name: PA15\nARM Peripheral: PWM TIM8_CH1

### HW15: Up Push Button (Functional)
ARM Pin Name: PB6\nARM Peripheral: GPIO_EXTI6

### HW16: Down Push Button (Functional)
ARM Pin Name: PC7\nARM Peripheral: GPIO_EXTI7

### HW17: Left Push Button (Functional)
ARM Pin Name: PC8\nARM Peripheral: GPIO_EXTI8

### HW18: Right Push Button (Functional)
ARM Pin Name: PC9\nARM Peripheral: GPIO_EXTI9

### HW19: Enter Push Button (Functional)
ARM Pin Name: PC5\nARM Peripheral: GPIO_EXTI5

## HW020: Power Supply (Functional)

### HW021: Battery Charge Sensor (Functional)
ARM Pin Name:PA7
ARM Peripheral: Bateria_AD

### HW022: Battery (Functional)
2200mAH 50C 11.1V Battery: Will power all robot components, ensuring voltage and current are adequate for motors, sensors, and the STM32 board.

### HW023: Step Down (Functional)

## HW024: Central Processing and Control (Functional)
STM32 Nucleo-64 NUCLEO-G474RE Board: Will control all sensors, motors, and communication interfaces. Responsible for processing sensor data, controlling motors via PWM, managing Bluetooth communication, and updating monitored parameters at a rate of 1 Hz.
